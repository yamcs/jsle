-- copied from
-- SPACE LINK EXTENSION—INTERNET PROTOCOL FOR TRANSFER SERVICES 
-- CCSDS 913.1-B-2 Page 3-1 September 2015 
-- https://public.ccsds.org/Pubs/913x1b2.pdf

CCSDS-SLE-TRANSFER-SERVICE-ISP1-CREDENTIALS
DEFINITIONS
IMPLICIT TAGS
::= BEGIN

ISP1Credentials  ::= --$ PDU SLE -- SEQUENCE
{ time         OCTET STRING (SIZE(8)) -- CCSDS CDS time code
, randomNumber INTEGER
, theProtected OCTET STRING (SIZE(20))
}

HashInput ::= SEQUENCE
 { time OCTET STRING (SIZE(8))
 , randomNumber INTEGER (0 .. 2147483647)
 , userName VisibleString
 , passWord OCTET STRING
 } 
END
