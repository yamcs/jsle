-- copied from
-- CCSDS RECOMMENDED STANDARD FOR SLE RCF SERVICE
-- CCSDS 911.2-B-3 Page A-24 August 2016
-- https://public.ccsds.org/Pubs/911x2b3.pdf
-- A2.7 SLE TRANSFER SERVICE—RCF OUTGOING PDUS

CCSDS-SLE-TRANSFER-SERVICE-RCF-OUTGOING-PDUS
{iso identified-organization(3) standards-producing-organization(112)
 ccsds(4) space-link-extension(3) sle-transfer-services(1)
 modules(1) return-channel-frames-service(13) version-four(4)
 asn1-outgoing-pdu(3)}
DEFINITIONS
IMPLICIT TAGS
::= BEGIN
IMPORTS Credentials
, IntUnsignedLong
, InvokeId
, SpaceLinkDataUnit
, Time
 FROM CCSDS-SLE-TRANSFER-SERVICE-COMMON-TYPES
 SleAcknowledgement
, SleScheduleStatusReportReturn
 FROM CCSDS-SLE-TRANSFER-SERVICE-COMMON-PDUS
 AntennaId
, CarrierLockStatus
, DiagnosticRcfGet
, DiagnosticRcfStart
, FrameSyncLockStatus
, LockStatus
, Notification
, RcfGetParameter
, RcfProductionStatus
, SymbolLockStatus
 FROM CCSDS-SLE-TRANSFER-SERVICE-RCF-STRUCTURES
 SleBindInvocation
, SleBindReturn
, SlePeerAbort
, SleUnbindInvocation
, SleUnbindReturn
 FROM CCSDS-SLE-TRANSFER-SERVICE-BIND-TYPES
;
-- =============================================================
-- The first part of the module definition contains the RCF type
-- that contains all the possible PDUs the provider may send.
-- ============================================================= 
RcfProviderToUserPdu ::= CHOICE
{ rcfBindInvocation [100] SleBindInvocation
, rcfBindReturn [101] SleBindReturn
, rcfUnbindInvocation [102] SleUnbindInvocation
, rcfUnbindReturn [103] SleUnbindReturn
, rcfStartReturn [1] RcfStartReturn
, rcfStopReturn [3] SleAcknowledgement
, rcfTransferBuffer [8] RcfTransferBuffer
, rcfScheduleStatusReportReturn [5] SleScheduleStatusReportReturn
, rcfStatusReportInvocation [9] RcfStatusReportInvocation
, rcfGetParameterReturn [7] RcfGetParameterReturn
, rcfPeerAbortInvocation [104] SlePeerAbort
}
-- =============================================================
-- The second part of the module definition contains the types
-- used by the RCF-PDUs declared in the first part.
-- =============================================================
FrameOrNotification ::= CHOICE
{ annotatedFrame [0] RcfTransferDataInvocation
, syncNotification [1] RcfSyncNotifyInvocation
}
RcfGetParameterReturn ::= SEQUENCE
{ performerCredentials Credentials
, invokeId InvokeId
, result CHOICE
 { positiveResult [0] RcfGetParameter
 , negativeResult [1] DiagnosticRcfGet
 }
}
RcfStartReturn ::= SEQUENCE
{ performerCredentials Credentials
, invokeId InvokeId
, result CHOICE
 { positiveResult [0] NULL
 , negativeResult [1] DiagnosticRcfStart
 }
}
RcfStatusReportInvocation ::= SEQUENCE
{ invokerCredentials Credentials
, deliveredFrameNumber IntUnsignedLong
, frameSyncLockStatus FrameSyncLockStatus
, symbolSyncLockStatus SymbolLockStatus
, subcarrierLockStatus LockStatus
, carrierLockStatus CarrierLockStatus
, productionStatus RcfProductionStatus
}
RcfSyncNotifyInvocation ::= SEQUENCE
{ invokerCredentials Credentials
, notification Notification
}
RcfTransferBuffer ::= SEQUENCE OF FrameOrNotification 
RcfTransferDataInvocation ::= SEQUENCE
{ invokerCredentials Credentials
, earthReceiveTime Time
, antennaId AntennaId
, dataLinkContinuity INTEGER (-1 .. 16777215)
, privateAnnotation CHOICE
 { null [0] NULL
 , notNull [1] OCTET STRING (SIZE (1 .. 128))
 }
, data SpaceLinkDataUnit
}
END
